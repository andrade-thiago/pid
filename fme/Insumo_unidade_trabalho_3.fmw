FME workspace Insumo_unidade_trabalho_3.fmw

Parameters:
- SourceDataset_POSTGIS = sap   # Nome banco de dados SAP
- HOST_POSTGIS =   # Host banco de dados SAP
- PORT_POSTGIS = 5432   # Porta banco de dados SAP
- USER_NAME_POSTGIS = controle_app   # Usuario banco de dados SAP
- PASSWORD_POSTGIS =   # Senha usuário banco de dados SAP
- RHS =   # grupo_insumo_id

Readers:
- POSTGIS_1: POSTGIS from $(SourceDataset_POSTGIS)

Writers:
- POSTGRES_1: POSTGRES to $(SourceDataset_POSTGIS)

insumo (reader POSTGIS_1)
    attributes: id int4,PrimaryKey, nome varchar(255), caminho varchar(255), epsg varchar(5), tipo_insumo_id int4, grupo_insumo_id int4
    -> Tester
Tester
    BOOL_OP = OR
    TEST_CLAUSE = TEST @Value(grupo_insumo_id) = $(RHS)
    PASSED -> AttributeRenamer
AttributeRenamer
    ATTR_TABLE = RENAME_SET_DEFAULT id > insumo_id
    -> SpatialFilter [Filter]
unidade_trabalho (reader POSTGIS_1)
    attributes: id int4,PrimaryKey, nome varchar(255),PrimaryKey, epsg varchar(5), banco_dados_id int4, subfase_id int4, lote_id int4, disponivel bool, prioridade int4
    -> AttributeRenamer_2
AttributeRenamer_2
    ATTR_TABLE = RENAME_SET_DEFAULT id > unidade_trabalho_id
    -> SpatialFilter [Candidate]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> insumo_unidade_trabalho (writer POSTGRES_1)
insumo_unidade_trabalho (writer POSTGRES_1)
    attributes: id serial,PrimaryKey, unidade_trabalho_id int4, insumo_id int4
