FME workspace unidade_trabalho.fmw

Parameters:
- SourceDataset_ECW =   # Imagens ECW
- HOST_POSTGIS =   # Host do banco do SAP
- PORT_POSTGIS = 5432   # Porta do banco do SAP
- DestDataset_POSTGIS = sap   # Nome do banco de dados do SAP
- USER_NAME_POSTGIS = controle_app   # Usuário do banco de dados
- PASSWORD_POSTGIS =   # Senha do usuário
- DEF_VAL = 1   # " " ID do banco de dados
- DEF_VAL_2 = 1   # " " ID da subfase
- DEF_VAL_3 = 1   # " " ID do lote
- DEF_VAL_4 = 31982   # " " EPSG de trabalho
- DEF_VAL_5 = true   # " " Unidades de trabalho devem ser disponíveis

Readers:
- ECW_1: ECW from $(SourceDataset_ECW)

Writers:
- POSTGIS_1: POSTGIS to $(DestDataset_POSTGIS)

Note: Le arquivos ECW, porém poderiam / ser Shapefiles, ou Geotiff
ECW (reader ECW_1)
    -> BoundingBoxReplacer
Note: Transforma o Geotiff e um polígono do seu bounding box
BoundingBoxReplacer
    BOXTYPE = 2D Bounding Box
    BOX -> Tiler
Note: Corta os polígonos em 4
Tiler
    BOUNDARY_CASES = No
    CLEANING_TOLERANCE = None
    COL_ATTR = _column
    GROUP_BY = fme_basename
    LINES_AS_SEGMENTS = No
    MEASURE_TYPE = Continuous
    MISSING_VAL_MODE = Compute
    NUM_HORIZONTAL_TILES = 2
    NUM_VERTICAL_TILES = 2
    ROW_ATTR = _row
    STARTINGCORNER = Lower Left
    TILING_TYPE = Number of Tiles
    TILED -> Bufferer
Note: Realiza um buffer para os poligonos terem uma pequena sobreposição
Bufferer
    ANGLE = 22.5
    CAP_STYLE = Round
    CORNER_STYLE = Round
    MODE = AREA
    OFFSET = 50
    BUFFERED -> Counter
Note: Contador para definir uma prioridade
Counter
    CNT_ATTR = _count
    DOMAIN = counter
    SCOPE = Global
    START = 1
    -> Reprojector_2
Note: Reprojeção para 4674
Reprojector_2
    DEST = EPSG:4674
    INTERPOLATION_TYPE_NAME = Nearest Neighbor
    RASTER_CELL_SIZE = Preserve Cells
    RASTER_TOLERANCE = 0.0
    SOURCE = Read from feature
    REPROJECTED -> AttributeCreator
Note: Cria os atributos necessários para inserir na camada unidade_trabalho
Note: EDITAR PADRÃO DE NOME
AttributeCreator
    ATTR_TABLE:
      SET_TO nome = @ReplaceString(@Value(fme_basename)_@Value(_count),"Ortoimagem_","")
      SET_TO epsg = $(DEF_VAL_4)
      SET_TO banco_dados_id = $(DEF_VAL)
      SET_TO subfase_id = $(DEF_VAL_2)
      SET_TO lote_id = $(DEF_VAL_3)
      SET_TO disponivel = $(DEF_VAL_5)
      SET_TO prioridade = @Value(_count)
    -> unidade_trabalho (writer POSTGIS_1)
Note: Grava no banco de dados do SAP
unidade_trabalho (writer POSTGIS_1)
    attributes: id serial,PrimaryKey, nome varchar(255),PrimaryKey, epsg varchar(5), banco_dados_id int4, subfase_id int4, lote_id int4, disponivel bool, prioridade int4
