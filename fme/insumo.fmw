FME workspace insumo.fmw

Parameters:
- SourceDataset_ECW =   # Imagens ECW
- DestDataset_POSTGIS = sap   # Banco de dados do SAP
- HOST_POSTGIS =   # Host do banco de dados do SAP
- PORT_POSTGIS =   # Porta do banco de dados do SAP
- USER_NAME_POSTGIS = controle_app   # Usuário de acesso ao SAP
- PASSWORD_POSTGIS =   # Senha do usuário do SAP
- DEF_VAL =   # " " tipo_insumo_id
- DEF_VAL_2 =   # " " epsg_insumo
- DEF_VAL_3 =   # " " grupo_insumo

Readers:
- ECW_1: ECW from $(SourceDataset_ECW)

Writers:
- POSTGIS_1: POSTGIS to $(DestDataset_POSTGIS)

Note: Leitura de imagens ECW
ECW (reader ECW_1)
    -> BoundingBoxReplacer
Note: Criação de polígonos utilizando o bounding box de cada imagem
BoundingBoxReplacer
    BOXTYPE = 2D Bounding Box
    BOX -> Reprojector_2
Note: Reprojeção para 4674
Reprojector_2
    DEST = EPSG:4674
    INTERPOLATION_TYPE_NAME = Nearest Neighbor
    RASTER_CELL_SIZE = Preserve Cells
    RASTER_TOLERANCE = 0.0
    SOURCE = Read from feature
    REPROJECTED -> AttributeCreator
Note: Criação dos atributos necessários da camada insumo
AttributeCreator
    ATTR_TABLE:
      SET_TO nome = @Value(fme_basename)
      SET_TO caminho = @Value(fme_dataset)
      SET_TO epsg = $(DEF_VAL_2)
      SET_TO tipo_insumo_id = $(DEF_VAL)
      SET_TO grupo_insumo_id = $(DEF_VAL_3)
    -> insumo (writer POSTGIS_1)
Note: Grava no banco do SAP
insumo (writer POSTGIS_1)
    attributes: id serial,PrimaryKey, nome varchar(255), caminho varchar(255), epsg varchar(5), tipo_insumo_id int4, grupo_insumo_id int4
